module clixon-eth-switch{
    yang-version 1.1;
    namespace "urn:idontknow:ethswitch";
    prefix eth-switch;

    import openconfig-vlan {
        prefix oc-vlan;
    }
    import openconfig-interfaces {
        prefix oc-if;
    }
    import openconfig-spanning-tree {
        prefix oc-stp;
    }

    revision 2025-09-23 {
	description
	    "Initial top-level Ethernet switch version";
    }
}
